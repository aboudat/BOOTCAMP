module loopback {

  namespace "http://example.com/loopback";
  prefix loopback;

  import ietf-inet-types {
    prefix inet;
  }
  import tailf-common {
    prefix tailf;
  }
  import tailf-ncs {
    prefix ncs;
  }

augment /ncs:services {

   list loopback {
    description "This is a loopback intf service";

    key name;
    leaf name {
      tailf:info "Service Instance Unique Name";
      type string;
    }

    uses ncs:service-data;
    ncs:servicepoint loopback-servicepoint;
  
    
    leaf device { 
        tailf:info "Name of the device";
        mandatory true;
        type leafref {
          path "/ncs:devices/ncs:device/ncs:name";
      }
     } 
    list loopback-intf {
        key loopback-intf;
        leaf loopback-intf {
        tailf:info "Loopback interface number from 1100 to 1199";
        mandatory true;
        type uint32 {
           range "1100..1199";
         }
        }
    leaf ip-address {
      tailf:info "Valid Ip-address from 10.100.x.x. to 10.199.x.x";
      mandatory true;
      type inet:ipv4-address {
        pattern  "10\\.1[0-9][0-9]\\.[0-9]+\\.[0-9]+";
      }
     }
    }
   }
  }
}
